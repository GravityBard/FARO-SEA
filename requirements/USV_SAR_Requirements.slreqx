# USV_SAR_Requirements

## NAV-001: Advance to the next search waypoint (Functional)
When the USV is within arrival_radius of the current search waypoint
and waypoint_index < num_waypoints, Route_Manager shall increment
waypoint_index by one at its next execution and output the coordinates
of the new waypoint.
At the last waypoint, waypoint_index shall remain equal to
num_waypoints.
- Rationale: Ensure ordered progression through the search route and prevent
  access beyond the waypoint array.

## SAR-001: Select the SAR target after detection (Functional)
While the mission is in Searching, if target_detected is true
and neither abort_mission nor battery_low is true,
the mission manager shall enter Approaching and set
target_found to true at its next execution.
With return_home false and target_found true, the target selector
shall output the SAR target position and velocity as the active
destination and set target_mode to 1.
- Rationale: Interrupt the search route to approach and track a detected
  SAR target, while preserving cancellation and low-battery priority.

## SAR-002: Confirm arrival using distance and relative speed (Functional)
For a destination requiring position holding, Arrival_Manager
shall set arrived to 1 only after both conditions remain
continuously satisfied for arrival_dwell_time seconds:
- distance_to_target <= arrival_radius.
- relative_speed <= arrival_speed.
If either condition is violated during confirmation,
Arrival_Manager shall keep arrived at 0 and restart the
confirmation period before declaring arrival.
- Rationale: Prevent arrival confirmation during a brief pass near the
  destination or while the USV is moving too quickly relative to it.

## SAR-003: Complete simulated assistance after uninterrupted on-scene residence (Functional)
While SAR_Mission_Manager remains continuously in On_Scene
for assistance_duration seconds, and neither abort_mission
nor battery_low is true, it shall set assistance_completed
to true at its first execution after that duration.
If the mission leaves On_Scene before assistance is completed,
a new full assistance period shall be required on re-entry.
Once true, assistance_completed shall remain true for the
remainder of the mission.
- Rationale: Represent assistance as an uninterrupted operation and retain
  a record of its completion during the return to base.

## SAFE-001: Prioritize return on cancellation or low battery (Functional)
While in Searching, Approaching, On_Scene or Search_Completed,
if abort_mission or battery_low is true, SAR_Mission_Manager
shall enter Returning_Home at its next execution and set
return_home to true and mission_status to 4.
This transition shall take priority over normal mission progression.
On entry to Returning_Home, return_reason shall be set to:
- 4 if battery_low is true.
- 3 otherwise, if abort_mission is true.
Once initiated, the return shall continue even if the triggering
signal becomes false.
- Rationale: Interrupt mission activities when return is requested and
  prevent an automatic resumption of the interrupted mission.

## END-001: Confirm mission completion after arrival at base (Functional)
While in Returning_Home, if arrived equals 1 and
(x-home_x)^2 + (y-home_y)^2 <= arrival_radius^2,
SAR_Mission_Manager shall enter Home_Reached at its next
execution and set:
- mission_status to 5.
- mission_completed to true.
- return_home to true.
mission_completed shall remain false before entering Home_Reached
and shall remain true for the remainder of the simulation run.
Entering Home_Reached shall preserve assistance_completed
and return_reason.
- Rationale: Record mission completion only after confirmed arrival at base,
  while retaining the assistance outcome and reason for return.

## ENE-001: Indicate low battery at the configured charge threshold (Functional)
Energy_Manager shall set battery_low to true when
battery_soc <= battery_return_soc, and to false when
battery_soc > battery_return_soc.
battery_soc shall be expressed as a fraction between 0 and 1.
The low-battery indication shall include equality at the threshold.
- Rationale: Provide a configurable low-charge indication to the mission manager
  without embedding the battery threshold in mission transitions.

## SEARCH-001: Rectangular search pattern generation (Functional)
The system shall generate an ordered sequence of waypoints forming an alternating sweep pattern within a rectangular area defined by its X and Y limits, with spacing between adjacent passes no greater than the configured value.
- Rationale: Generating the search route from configurable area limits and pass spacing avoids manually editing waypoint lists and supports reuse across different search areas. Alternating pass directions produces a continuous sweep route.

## SEARCH-002: Search pass spacing constraint (Functional)
The system shall reject a search configuration when the maximum pass spacing exceeds twice the difference between the configured detection range and the configured lateral tracking error allowance. The allowance shall be non-negative and smaller than the detection range.
- Rationale: Under the ideal circular detection model, lateral tracking errors can leave gaps between adjacent search passes. Limiting pass spacing to twice the detection range minus twice the lateral tracking error allowance reserves a geometric margin against such gaps. This constraint does not guarantee actual coverage if the allowance is exceeded or the detection assumptions are not met.

## SEARCH-003: Search area coverage estimation (Functional)
The analysis shall estimate search area coverage as the percentage of points in a uniformly spaced grid covering the configured rectangular area that lie within the configured detection range of at least one recorded true USV position during the Searching mission state (mission_status = 0). The grid spacing shall be configurable.
- Rationale: Waypoint geometry alone does not establish the coverage achieved by the vessel. A grid-based metric allows comparison of search trajectories, including deviations caused by navigation outages. Using true position provides a simulation reference independent of navigation estimation errors. The result assumes ideal circular detection and is an approximation whose resolution depends on the grid spacing.

## SAR-004: Valid contact required for assistance confirmation (Functional)
While assisting the MOB, the mission manager shall leave the On_Scene state no later than its next execution after contact_valid becomes false. Assistance shall only resume after contact validity and the arrival conditions have been confirmed again.
- Rationale: Assistance must not remain confirmed when the target is no longer observed. Separating contact validity from own-vessel navigation validity allows target sensor failures and GNSS failures to be handled independently.

## SAR-005: Bounded MOB prediction and guidance permission (Functional)
After receiving a valid MOB observation, the system shall estimate
the MOB position and velocity.
During contact loss, the estimator shall predict the MOB motion
and report the elapsed time since the last accepted observation.
Tracking shall be marked invalid before the first accepted
observation and whenever the observation age exceeds
mob_track_max_age.
While pursuing the MOB, guidance shall require both valid own-ship
navigation and valid MOB tracking. An expired MOB track shall
not inhibit return-home guidance when own-ship navigation is valid.
When a valid MOB observation is accepted again, the observation
age shall reset to zero and tracking shall become valid.
- Rationale: Brief contact interruptions should permit bounded predictive
  guidance. Stale target estimates must not be used indefinitely,
  and loss of MOB tracking must not prevent a safety return.
